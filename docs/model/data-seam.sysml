// plane: workflow | system: fetcher
//
// The data seam as a checkable model: the bed under a hydraulic run.
//
// SysML v2 TEXTUAL notation, restricted to the subset the project checker
// reads. Conventions as the other seams: ``code:`` binds a block to the module
// it IS, ``forbid:`` states a dependency rule, ``constructor:`` names a
// function that builds a contract, and ``pass-through:`` marks an end that
// forwards a contract verbatim.
//
// This seam exists because a bed is the one input a model cannot be honest
// without and cannot check for itself. Every requirement below is a decision
// from the bathymetry methodology (docs/local/research/bathymetry-sources.md), named
// in its doc, allocated to the code that embodies it and verified by a test
// that exists.

package DataSeam {

    doc /*
    An elevation surface is not a bed. A DEM measures the water TOP where the
    channel is wet, and reading one as a channel bottom systematically
    under-represents conveyance - a BIAS, not noise, worst on exactly the small
    streams where the substitution is most tempting. So each bed row states what
    it measured, over what footprint, at what cell and on which zero, and the
    match ranks those statements: what painted the bed and on what vertical
    datum travels with the layer, because a bed whose datum nobody carried is a
    bed nobody can merge.
    */

    // ----------------------------------------------------------------- //
    // Blocks
    // ----------------------------------------------------------------- //

    part def KeyedSourceDeclaration {
        doc /*
        A row that needs a key. It states WHICH key, by name, beside the
        endpoints it needs the key for - so nothing downstream keeps a table of
        which source needs what.
        */
    }

    part def CredentialResolver {
        doc /*
        The one reader of a row's credential. It resolves a key for a
        keyed tool - the session's pushed key first, the row's own env var
        behind it - and refuses by name when neither holds one, because a keyed
        call with no key cannot succeed and a refusal that names the credential
        is the only honest thing left to say.
        */
    }

    part def KeyedSourceCatalog {
        doc /*
        What the daemon tells a key-entering surface: the credential each source
        row declares, by name, with no key material. It restates nothing - the
        rows are the closed set and this is a projection of them.
        */
    }

    part def CredentialStore {
        doc /*
        The session's own credential home. A key entered here reaches the daemon
        only as a pushed value for a bespoke fetcher; for a borrowed provider it
        never leaves at all, and the stored config id rides the datasource uri.
        */
    }

    part def KeysForm {
        doc /*
        One masked row per credential the rows declare, not per source,
        so two sources served by one account are one row and one entered key.
        The chat is never a key path.
        */
    }

    part def BorrowedProviderExecutor {
        doc /*
        The daemon end of a borrowed provider row: it names which credential the
        row needs and never resolves it, so no keyed row can put a key on the
        wire.
        */
    }

    part def BorrowedProviderSession {
        doc /*
        The session end: it attaches its OWN stored config to the uri, and
        refuses by name toward the keys form when nothing is stored under the
        credential the row asked for.
        */
    }

    part def FetcherRouter {
        doc /*
        The door a data ask enters: one row, validated, gated,
        dispatched, cached and emitted.
        */
    }

    part def CatalogRasterReader {
        doc /*
        The reader a catalog-published raster row is served by. It takes the
        row's catalog coordinates - which collection, which asset, at which
        cell, signed how, rendered how - and returns the window. It knows
        nothing about the DATA: the vertical datum, the resolution and the style
        stay on the row, because a library that fetches bytes cannot say
        what they are referenced to.
        */
    }

    part def BlueTopoSource {
        doc /*
        NOAA's National Bathymetric Source as a fetchable bed: the published
        tile scheme intersected with the AOI, each tile gated on its stated
        datum, merged onto one grid.
        */
    }

    part def BedPainter {
        doc /*
        The op that puts a source's elevations onto a mesh's nodes: it asks the
        row for its datum before it fetches, journals what actually
        painted, and refuses a bed that came back on two vertical references.
        */
    }

    part def BedSourceDeclaration {
        doc /*
        A bed source's declaration - its params, its hooks and its caveats.
        Data, not code.
        */
    }

    part def FreeSurfaceReader {
        doc /*
        The slot ingestion that turns an observed water level into the elevation
        a run opens at: it ranks the reporting sites against the domain, takes
        the nearest reading in the unit the keyword reads, and says on the run
        journal which site reported it and when.
        */
    }

    part def SeaStateReader {
        doc /*
        The slot ingestion that turns a buoy's record into the one sea state it
        measured: the column stated in each quantity's own unit, read at the
        moment the run opens at - a height, a peak period and the bearing the
        waves come from, with the buoy that reported them.
        */
    }

    part def WeatherReader {
        doc /*
        The slot ingestion that turns a station record into one station's
        series: the nearest station whose record brackets the run's window,
        every quantity its network reports as a series of its own in the unit
        its name states, on a clock that reads zero where the run opens, and
        the reason beside any quantity that station is short of.
        */
    }

    part def RainReader {
        doc /*
        The slot ingestion that turns a rainfall record into the depth that
        fell in each interval, in millimetres, on the run's clock: the instants
        and the cadence are the record's own, the column and its unit the
        matched row's statement.
        */
    }

    part def WaterCut {
        doc /*
        The derive that turns a box and a mapped coastline into the WATER inside
        it: the faces the ways split the box into, classified by the direction
        each way was drawn, with the wet ones returned as one polygon.
        */
    }

    part def CacheRetention {
        doc /*
        What the read-through cache keeps of the data a run stood on: the uris a
        live case pins through the runs it published, and the sweep that deletes
        every object neither pinned nor still inside its own TTL class's window.
        */
    }

    part def ObjectStore {
        doc /*
        The one client every read and write of the object store goes through,
        built from the store's own endpoint and key pair and nothing a shell
        happened to inherit.
        */
    }

    part def BedResultModel {
        doc /*
        The layer a bed fetch returns, with the provenance fields that are NOT
        recoverable from the raster bytes - which tiles painted it, at which
        tiers, over what share of the AOI, and on which vertical datum.
        */
    }

    // ----------------------------------------------------------------- //
    // Ports
    // ----------------------------------------------------------------- //

    port def ProvenanceOut;
    port def ProvenanceIn;
    port def DeclarationOut;
    port def DeclarationIn;
    port def CredentialOut;
    port def CredentialIn;
    port def KeyedCatalogOut;
    port def KeyedCatalogIn;
    port def LayerCredentialOut;
    port def LayerCredentialIn;

    // ----------------------------------------------------------------- //
    // Interfaces - the seam contracts, by their real key names
    // ----------------------------------------------------------------- //

    interface def BedProvenance {
        doc /*
        What a bed fetch knows and the bytes do not. The DATUM is the load-
        bearing one: BlueTopo is on NAVD88, an orthometric datum and explicitly
        not a navigational or tidal one, which is the whole reason it merges
        with a NAVD88 land DEM with no transformation. ``coverage_fraction`` is
        below 1.0 for any AOI holding land, by construction, and saying so is
        the honest report rather than a failure.

        constructor: BlueTopoResult
        */
        item vertical_datum : String;
        item tile_count : Integer;
        item resolution_tiers : StringList;
        item coverage_fraction : Real;
        item rung_coverage : Map [0..1];
    }

    interface def BedSourceParams {
        doc /*
        The request a bed source takes. ``resolution_m`` is the one lever name
        every raster fetcher shares: it floors the merge at the asked cell size,
        never invents a cell finer than the tile that was read and never
        coarsens past the ask, which is why it is the param the resolution
        declaration hangs off.
        */
        item bbox : RealList;
        item target_crs : String;
        item timeout_s : Real;
        item resolution_m : Real [0..1];
    }

    interface def CatalogReadDeclaration {
        doc /*
        What a row tells a catalog reader. Every key is a coordinate INTO
        a catalog, never a claim about the pixels: the reader can find the asset
        and put it on a grid, and it still cannot say which datum the numbers
        are on. That is why a bed source published through a catalog states its
        datum on its own row and the reader carries none.
        */
        item collection : String;
        item data_asset : String;
        item native_cell_m : Real;
        item render : String;
        item sign : String;
    }

    interface def SourceCredentialDeclaration {
        doc /*
        The key a source needs, stated where the source is. ``name`` is the
        SCOPE a stored key lands under, which is why two rows served by one
        upstream account state the same name; ``env_var`` is the same variable
        the source's own hook reads, so the form and the code cannot disagree
        about which key this is.
        */
        item name : String;
        item label : String;
        item env_var : String;
    }

    interface def LayerCredentialRef {
        doc /*
        Which credential a borrowed provider row needs, by NAME only. The
        session resolves it in its own store, so this is the whole of what the
        daemon can say about a keyed provider row and the key itself never
        crosses the wire in either direction.
        */
        item credential : String [0..1];
    }

    // ----------------------------------------------------------------- //
    // Parts - bound to the modules they ARE
    // ----------------------------------------------------------------- //

    part fetcherRouter : FetcherRouter {
        doc /*
        code: trid3nt_server/tools/fetchers/_router/router.py
        */
    }

    part stacRasterReader : CatalogRasterReader {
        doc /*
        code: trid3nt_server/tools/fetchers/_router/executors/stac_raster.py
        */
        port declarationIn : DeclarationIn;
    }

    part copernicusDeclaration : BedSourceDeclaration {
        doc /*
        code: trid3nt_server/tools/fetchers/terrain/fetch_copernicus_dem/source.yaml
        */
        port declarationOut : DeclarationOut;
    }

    part blueTopoSource : BlueTopoSource {
        doc /*
        code: trid3nt_server/tools/fetchers/ocean/fetch_bluetopo/hooks.py
        */
        port declarationIn : DeclarationIn;
        port provenanceOut : ProvenanceOut;
    }

    part blueTopoDeclaration : BedSourceDeclaration {
        doc /*
        code: trid3nt_server/tools/fetchers/ocean/fetch_bluetopo/source.yaml
        */
        port declarationOut : DeclarationOut;
    }

    part cudemDeclaration : BedSourceDeclaration {
        doc /*
        code: trid3nt_server/tools/fetchers/ocean/fetch_cudem/source.yaml
        */
    }

    part regionalCoastalDemDeclaration : BedSourceDeclaration {
        doc /*
        code: trid3nt_server/tools/fetchers/ocean/fetch_regional_coastal_dem/source.yaml
        */
    }

    part nceiTsunamiDemDeclaration : BedSourceDeclaration {
        doc /*
        code: trid3nt_server/tools/fetchers/ocean/fetch_ncei_tsunami_dem/source.yaml
        */
    }

    part etopoDeclaration : BedSourceDeclaration {
        doc /*
        code: trid3nt_server/tools/fetchers/ocean/fetch_etopo/source.yaml
        */
    }

    part firmsDeclaration : KeyedSourceDeclaration {
        doc /*
        code: trid3nt_server/tools/fetchers/hazard/fetch_firms_active_fire/source.yaml
        */
        port credentialOut : CredentialOut;
    }

    part credentialResolver : CredentialResolver {
        doc /*
        code: trid3nt_server/model/credentials/resolver.py
        */
        port credentialIn : CredentialIn;
        port keyedCatalogOut : KeyedCatalogOut;
    }

    part keyedSourceCatalog : KeyedSourceCatalog {
        doc /*
        code: trid3nt_server/server/protocol/http/library.py
        */
        port keyedCatalogIn : KeyedCatalogIn;
        port credentialOut : CredentialOut;
    }

    part keysForm : KeysForm {
        doc /*
        code: plugin/ui/settings_dialog.py
        */
        port credentialIn : CredentialIn;
    }

    part credentialStore : CredentialStore {
        doc /*
        code: plugin/net/auth_broker.py
        */
    }

    part borrowedProviderExecutor : BorrowedProviderExecutor {
        doc /*
        code: trid3nt_server/tools/fetchers/_router/executors/qgis_provider.py
        */
        port layerCredentialOut : LayerCredentialOut;
    }

    part borrowedProviderSession : BorrowedProviderSession {
        doc /*
        code: plugin/render/layer_request.py
        */
        port layerCredentialIn : LayerCredentialIn;
    }

    part waterCut : WaterCut {
        doc /*
        code: trid3nt_server/tools/mesh/water.py
        */
    }

    part coastlineDeclaration : BedSourceDeclaration {
        doc /*
        code: trid3nt_server/tools/fetchers/socioeconomic/fetch_osm_features/source.yaml
        */
    }

    part bedPainter : BedPainter {
        doc /*
        code: trid3nt_server/tools/mesh/shared/primitives.py
        */
    }

    part def DomainSlot {
        doc /*
        The one row a run is solved over: a closed polygon, geometry only.
        Drawn, picked, fetched or purely surveyed, it reads the same afterwards.
        */
    }

    part def BedSlot {
        doc /*
        The one row every node's elevation comes from: a surface or a stated
        depth. A layer of soundings is laid on the bed grid and filled by the
        bed's own fill.
        */
    }

    part def BedComposer {
        doc /*
        The bed slot's own coercion over an ORDERED LIST of surfaces, each
        already read on the run's frame: laid onto one grid, the earlier handed
        winning every cell it measured, and what nothing measured inside the
        cut filled by the bed settings. Every fetched layer carries its vertical
        datum, its quantity and the shift its source publishes about that datum
        as fields on the layer record - a source whose rows each state their
        zero is stamped off what its rows agree on - and a layer named by id
        brings them along. QGIS's IDW, run through run_qgis_algorithm, grids
        soundings, and its output is a case layer carrying the fields its input
        carried. The laid bed writes a second band naming where every cell came
        from - a surface's place in the list, or filled - which the mesh reads
        to journal the share of nodes each surface painted.
        */
    }

    part def BoundaryRunSlot {
        doc /*
        The named stretches of the domain's edge, each two points and a type.
        Zero of them is an answer: a closed body's edge is solid wall whole.
        */
    }

    part def LineSlot {
        doc /*
        The polyline a placed read is measured ALONG: the centerline a domain's
        producer measured beside its polygon, or the line a user draws over a
        body whose producer measured none. Optional by construction - a run
        solves without one - and read by purpose on the canvas when it is not.
        */
    }

    part def ExtentSlot {
        doc /*
        The RECTANGLE a question is asked inside - the window a domain is cut
        out of - however the caller names it: a box picked on the canvas, four
        numbers, a place, or a layer's bounds.
        */
    }

    part def VerticalFrame {
        doc /*
        The ONE zero a run counts every elevation from, and the coercion that
        brings a source published on another onto it.
        */
    }

    part def SourceCoverage {
        doc /*
        A source's ONLY statement of what it covers: the class of thing it
        measures, how it came by its numbers, where and how far one station
        serves, over what time, at what cell, on what zero, and the unit of each
        value column. Stated from the dataset's own documentation.
        */
    }

    part def SlotNeed {
        doc /*
        What a slot asks the world for: one class of the coarse vocabulary. The
        place, the window and the frame are the RUN's and are read off it, so a
        question states none of them.
        */
    }

    part def SourceMatch {
        doc /*
        The one function that reads a need against every row: class and
        place hard, the window hard for a series and a sort key for a surface,
        the datum flagged. Pure over declarations; the caller probes.
        */
    }

    part def SourceDoor {
        doc /*
        The one way the model reaches a data source: find_sources fills each
        row (a ranked class at a place, or free text) through the same filler a
        template's need row uses and holds the request under a handle S<n> the
        case never reuses; fetch sends a row by its handle, with edits checked
        against the names its source declares and re-checked for what it
        reaches, or calls a source by name with its own arguments. A source is
        no tool of the prompt, the retrieval index or a declared set.
        */
    }

    part def RankedSourceList {
        doc /*
        ONE object in three views: the card renders it with the pick
        highlighted, the tool result carries the rows on a tie, and the sheet
        stores the pick and its reason.
        */
    }

    part domainSlot : DomainSlot {
        doc /*
        code: trid3nt_server/inputs/domain.py
        */
    }

    part bedSlot : BedSlot {
        doc /*
        code: trid3nt_server/inputs/bed.py
        */
    }

    part bedComposer : BedComposer {
        doc /*
        code: trid3nt_server/inputs/bed_merge.py
        */
    }

    part boundaryRunSlot : BoundaryRunSlot {
        doc /*
        code: trid3nt_server/inputs/boundary.py
        */
    }

    part slotDoor : DomainSlot {
        doc /*
        code: trid3nt_server/inputs/slots.py
        */
    }

    part lineSlot : LineSlot {
        doc /*
        code: trid3nt_server/inputs/line.py
        */
    }

    part extentSlot : ExtentSlot {
        doc /*
        code: trid3nt_server/inputs/extent.py
        */
    }

    part coverageContract : SourceCoverage {
        doc /*
        code: contracts/trid3nt_contracts/coverage.py
        */
    }

    part gaugeDeclaration : SourceCoverage {
        doc /*
        code: trid3nt_server/tools/fetchers/hydrology/fetch_usgs_nwis_gauges/source.yaml
        */
    }

    part needDeclaration : SlotNeed {
        doc /*
        code: trid3nt_server/inputs/input.py
        */
    }

    part sourceMatch : SourceMatch {
        doc /*
        code: trid3nt_server/tools/search/match.py
        */
    }

    part matchedSlot : SourceMatch {
        doc /*
        code: trid3nt_server/workflows/runtime/fill.py
        */
    }

    part modelMatch : SourceMatch {
        doc /*
        code: trid3nt_server/tools/search/find_sources/find_sources.py
        */
    }

    part sourceDoorFind : SourceDoor {
        doc /*
        code: trid3nt_server/tools/search/find_sources/find_sources.py
        */
    }

    part sourceDoorFetch : SourceDoor {
        doc /*
        code: trid3nt_server/tools/search/fetch/fetch.py
        */
    }

    part rankedListCard : RankedSourceList {
        doc /*
        code: trid3nt_server/workflows/telemac/workflow.py
        */
    }

    part rankedListRecord : RankedSourceList {
        doc /*
        code: trid3nt_server/workflows/runtime/journal.py
        */
    }

    part seriesOnTheRunsClock : FreeSurfaceReader {
        doc /*
        code: trid3nt_server/inputs/temporal.py
        */
    }

    part verticalFrame : VerticalFrame {
        doc /*
        code: trid3nt_server/inputs/vertical_datum.py
        */
    }

    part frameLever : VerticalFrame {
        doc /*
        code: trid3nt_server/inputs/slots.py
        */
    }

    part lakeDeclaration : BedSourceDeclaration {
        doc /*
        code: trid3nt_server/tools/fetchers/ocean/fetch_greatlakes_bathymetry/source.yaml
        */
    }

    part lakeLevelDeclaration : BedSourceDeclaration {
        doc /*
        code: trid3nt_server/tools/fetchers/ocean/fetch_greatlakes_water_level/source.yaml
        */
    }

    part freeSurfaceReader : FreeSurfaceReader {
        doc /*
        code: trid3nt_server/inputs/observation.py
        */
    }

    part seaStateReader : SeaStateReader {
        doc /*
        code: trid3nt_server/inputs/wave.py
        */
    }

    part weatherReader : WeatherReader {
        doc /*
        code: trid3nt_server/inputs/weather.py
        */
    }

    part rainReader : RainReader {
        doc /*
        code: trid3nt_server/inputs/rain.py
        */
    }

    part offsetRowDeclaration : VerticalFrame {
        doc /*
        code: trid3nt_server/workflows/runtime/fill.py
        */
    }

    part bedResultModel : BedResultModel {
        doc /*
        code: contracts/trid3nt_contracts/execution.py
        */
        port provenanceIn : ProvenanceIn;
    }

    part cacheRetention : CacheRetention {
        doc /*
        code: trid3nt_server/store/sweep.py
        */
    }

    part objectStore : ObjectStore {
        doc /*
        code: trid3nt_server/store/objects.py
        */
    }

    // ----------------------------------------------------------------- //
    // Hops
    // ----------------------------------------------------------------- //

    interface bedSourceDeclared : BedSourceParams
        connect blueTopoDeclaration.declarationOut to blueTopoSource.declarationIn;

    interface catalogBedDeclared : CatalogReadDeclaration
        connect copernicusDeclaration.declarationOut to stacRasterReader.declarationIn;

    interface bedProvenanceCarried : BedProvenance
        connect blueTopoSource.provenanceOut to bedResultModel.provenanceIn;

    interface sourceCredentialDeclared : SourceCredentialDeclaration
        connect firmsDeclaration.credentialOut to credentialResolver.credentialIn;

    interface keyedRowsProjected : SourceCredentialDeclaration
        connect credentialResolver.keyedCatalogOut to keyedSourceCatalog.keyedCatalogIn;

    interface keysFormOffersTheRows : SourceCredentialDeclaration
        connect keyedSourceCatalog.credentialOut to keysForm.credentialIn;

    interface layerCredentialNamed : LayerCredentialRef
        connect borrowedProviderExecutor.layerCredentialOut
            to borrowedProviderSession.layerCredentialIn;

    // ----------------------------------------------------------------- //
    // The signed decisions this seam is governed by
    // ----------------------------------------------------------------- //

    requirement def AKeyedSourceStatesTheKeyItNeeds {
        doc /*
        The key a source needs is a fact ABOUT THE SOURCE, so it is stated on
        the source's own row and nowhere else - name, label and the env var the
        source's own hook reads; no signup link is kept on a row, and one is
        shown only when the provider's own answer carries it. Everything downstream is a reader
        of those rows: the resolver takes the session's pushed key first and the
        row's env var behind it, the catalog projects the rows for a
        key-entering surface, and the keys list shows one entry per credential
        NAME rather than per source, so two sources served by one upstream
        account take one entered key.

        A keyed call with no key stored, or one the provider refuses, is asked
        of the person on a card and runs once more with the key the card
        stored; the refusal names the credential and the source and never a
        value. The chat is never the place a key is entered: a key pasted into
        a conversation is a key in the model's context and in the history, so
        the card and the settings list are the only surfaces that take a value
        and the model reads no argument that could carry one.
        */
    }

    requirement def AKeyedProviderRowsKeyNeverLeavesTheSession {
        doc /*
        A borrowed provider row states which credential it needs and the daemon
        stops there. The session resolves that name in its OWN credential store
        and attaches the stored config as the uri's ``authcfg=`` token, so the
        key is never on the wire, never in a log and never in the daemon's
        memory. A row whose credential nothing has stored is refused by name
        toward the keys form rather than opened - the provider's own rejection
        would name neither the credential nor where a key is entered.
        */
    }

    requirement def ACatalogReaderCarriesNoProvenance {
        doc /*
        The STAC rows read through a maintained catalog library rather than
        hand-written search-and-warp code. The library owns the socket, the
        grid and the pixel fuse; it owns nothing else. Provenance facts - the
        vertical datum, the resolution and the style row - stay on the source
        row whatever library performs the fetch, so a bed published through a
        catalog is as mergeable after the fold as before it.
        */
    }

    requirement def BedSourceStatesItsDatum {
        doc /*
        SIGNED DECISION - the bed's vertical datum is stated in provenance, not
        assumed by a reader. BlueTopo publishes NAVD88 and says so twice in each
        tile; a tile that states neither is refused rather than merged, because
        the whole reason this source outranks the alternatives is that its datum
        is known. The datum, the tiles, the tiers and the measured coverage ride
        on the returned layer, since none of them survives in the raster bytes.
        */
    }

    requirement def OneSourceReadsOnOneStatedDatum {
        doc /*
        Every bed source states its VERTICAL DATUM on its own row, taken
        from the dataset's own documentation and never inferred from the bytes
        - a raster carries numbers, and what they are counted from is not among
        them. A row that cannot state one carries none, and a row carrying none
        is refused as a bed rather than painted and read later as if it were on
        whatever the run assumed.

        A mosaic that mixes datums is therefore not a bed source. The NCEI
        DEM_all endpoint serves the lake-datum bathymetry, the NAVD88 coastal
        tiles, the same tiles on MHW and the EGM2008 global bases merged under
        one name, so the row that reads it as a bed pins the ONE product it
        means and states that product's datum.

        The stated datum is the WHOLE guard. A post-paint population test over
        the elevations is not one: real terrain puts an outlier as far from its
        neighbours as a datum offset does, so such a test reads the shape of the
        ground rather than the reference it is counted from.

        The datum rides onto the layer's provenance card beside the acquisition
        instant, since a bed the user is shown to refine is
        a bed they may stitch another source onto, and that is the metadata the
        two have to be compared on.

        THE ROW STATES A FRAME NAME. The zero on a row is one of the
        names the offset service converts between, the per-record word where
        each feature carries its own, or nothing at all. It is what an offset
        is asked in, so prose - "each Great Lake's own Low Water Datum" - names
        a surface nothing can bring another onto and the row loader refuses it
        naming the row. The vocabulary is read off the offset fetch's own
        params, because a second list of frame names would drift from the one
        service that has to answer for them. What a SUPPLIED layer says is not
        governed here: a document states its zero in its own words, and the
        fullest frame those words name is what is asked for.
        */
    }

    requirement def AFreeSurfaceAndABedShareOneStatedDatum {
        doc /*
        A water body's LEVEL is an observation, fetched the way a river's
        discharge is - the nearest gauge to the AOI, at the day the run is
        about - and the run's free surface opens at it. Data is assumed true;
        nothing thresholds the reading.

        WHAT MAKES THE ARITHMETIC LEGAL is that both documents state their zero.
        The gauge row and the bed row each state a vertical datum, and the
        subtraction between a level and an elevation is only defined when the
        two statements agree. Two rows stating different zeros, with no offset
        stated anywhere, REFUSE BY NAME - both names and both datums - rather
        than adding numbers that are not on one axis. A row stating none refuses
        for the reason OneSourceReadsOnOneStatedDatum already gives.

        Left at the dictionary's own zero the free surface sits ON the chart
        datum, which is where the bed is counted from, so the rim of a surveyed
        basin carries no water at all. Clipping that rim away would be a
        threshold on values; giving it its real water is the observation.
        */
    }

    requirement def WaterNothingMeasuredIsFilledOnlyWithinTheStatedReach {
        doc /*
        NOTHING PAINTS SILENTLY. The bed lays the row the match ranked
        first and each next ranked row while the water is left a wet hole, or the ordered list of surfaces it was handed, and STATES WHAT IT COVERS - over the water the domain was cut with
        and over the land separately, what each row painted there and what
        nothing measured, and the rows that also matched and could cover the
        gap. A wider surface over the water measures its TOP, so it is not a bed
        there: a row serving terrain paints outside the cut polygon only. The
        feedback is the whole of what the slot hands a person, and it is stated
        BEFORE THE SOLVE where they meet the fill: on the run's own card beside
        the sources it matched, and on the journal.

        A WET HOLE PAST THE FILL'S REACH REFUSES BY NAME AT THE FILL. Water
        inside the cut that no surface measured - including water past every
        surface's own edge - is filled from the cells measured inside the cut
        alone, by the interpolator the FILL_ALGORITHM setting names, no farther
        than FILL_MAX_DISTANCE pixels from a measured cell; each filled cell is
        marked filled in the second band, so an interpolation is never read as
        a sounding, and the share filled is stated with the coverage. Water
        past that reach has no bed, and the slot refuses naming where it
        stands, the setting that would reach it and a further surface handed
        after these. A DRY hole is stated and left to the mesh, which refuses a
        node no value reaches.

        A FURTHER SURFACE IS THE PERSON'S STATEMENT. No workflow is baked in:
        the person or the model reads the coverage, hands the bed a further
        surface in an ordered list - a layer, or a source fetched under the
        class it serves - or stops. The earlier handed wins every cell it
        measured and a later one paints only what the earlier left; the seam
        between them is blended over the MERGE_BUFFER_CELLS setting. The age
        between the surfaces is stated beside their coverage. An engine that
        lays its own ladder of surfaces and takes the finest at each point takes
        one surface on its bed row and neither merges nor fills.
        */
    }

    requirement def AConsumedObjectIsPinnedWhileItsCaseLives {
        doc /*
        An object a run consumed is pinned by that run's journal record for as
        long as a case still holds one of the layers the run published, so a
        case reopened long after answers from the same bytes it was answered
        with. A case deleted releases what it held.

        Everything else ages by the TTL class its own key was salted with: past
        that window the key can no longer be computed, so the bytes are already
        unreachable and the sweep is only what makes unreachable mean gone. An
        object and the provenance sidecar beside it share one fate, because a
        pinned object whose sidecar went is a miss. Only the cache is swept: a
        run's own products carry no class to age by.
        */
    }

    requirement def TheStoreIsReachedByItsOwnSettings {
        doc /*
        The store's endpoint, key pair and region are passed to the client
        explicitly, from the stack's settings file first and the process
        second, so ambient credentials the store has never heard of are never
        what a write carries. A store with no endpoint stated refuses by name
        rather than reaching for a cloud nobody named.
        */
    }

    requirement def TheRunHasOneVerticalFrame {
        doc /*
        A run counts every elevation it ingests from ONE zero, and that zero is
        the BED's: its type declares the frame beside its row, NAVD88 by
        default, and the level and every matched need read that one - never a
        row a question writes. A template that named its own datum would
        make the frame a property of the question rather than of the run, and
        two questions over one water body would then answer on two axes.

        A source published on another frame reaches the run's through a shift
        somebody MEASURED, in one order: the shift the source publishes about
        itself - a district's project datum states in the survey's own metadata
        how far it sits above a national frame, and no service serves that -
        else the offset a DATA ROW produces between the two frames at a point
        the OWING SOURCE has data at - the point of that source's own footprint
        nearest the question's seed, the seed itself where it lies inside that
        footprint, and never a box's centre or a polygon's centroid. A datum
        relation is a shift and not a field, so one point stands for the whole
        source and the row states WHICH point it was asked at, which is what a
        reader needs to dispute it; a footprint the service reaches nowhere
        refuses naming that point. That row is the RUNTIME's: it is declared where an
        elevation slot is handed a source on another frame, walked and journaled
        like any other producer, and the slot's coercion reads its value and
        fetches nothing - a coercion may call a derive, never a fetch. A pair
        nothing measures refuses naming BOTH frames rather than laying one over
        the other, because a shift nobody measured is indistinguishable from a
        measurement to every reader downstream.

        The zero is the one the RECORD states. A source whose every feature
        carries its own says so on its row in the per-record form
        rather than stating nothing, and what is aligned states the zero the
        rows state - a refusal that read the holder instead would say a survey
        states no datum while its every row states one. A stated zero is asked
        for by the FULLEST frame its words name: a chart datum names the
        reference system it is expressed on, and a low water plane is not the
        geodetic zero it is expressed on but a surface metres above it, so the
        shorter name inside the longer is never what is measured. A DEPTH is
        counted from a WATER SURFACE and never from a reference system, so the
        word a record of depths states names the surface it hangs below: a
        sounding on IGLD85 is counted from the low water datum expressed on
        IGLD85, which the row's own datum vocabulary says and the survey's plot
        sheet states in its own sentence.

        The same order holds for every surface of an ordered list handed the
        bed: EACH is read onto the run's frame through the shift it publishes or
        its own offset row before any of them paints a cell, and a pair nothing
        bridges refuses naming both. A surface counting DEPTHS down from its zero is one
        axis with a surface counting elevations up only through that shift, so
        it is read the other way round on the way - on its own grid, before
        either is read onto the common one.

        What a slot does with a source that states NO datum is that slot's own
        statement and not this one's: a surface of depths has to know the zero
        they are counted below and refuses without it, while an elevation
        surface somebody handed this run stands on the run's frame.

        AN UNPLACEABLE INPUT REFUSES. An input whose zero no offset row reaches
        the run's frame from refuses by name, naming both zeros. The refusal is
        built ONCE, by the datum check that knows both zeros; a slot re-raises
        it under its own code rather than restating the surface and the two
        frames in its own words, since two statements of one fact are two
        chances to disagree.

        A BED THAT SPLIT IN TWO IS REFUSED BY NAME. A shift nobody caught still
        shows in what the rows painted: values in two populations farther apart
        than the relief of the surface under them is a step no ground holds, and
        every node is painted, so nothing below catches it. The merge refuses,
        naming both ranges and the row each came from, rather than handing a
        mesh a cliff for a river to stand in. The domain's OWN relief is the
        yardstick, because the only number that says how far this landscape
        falls is this landscape.
        */
    }

    requirement def ASourceStatesWhatItCovers {
        doc /*
        A fetcher's row is its ONLY statement of coverage: the class of
        thing it measures, the place it reaches as a coarse polygon or a station
        set or "read from the service", the time its records span, the cell it
        publishes at, the zero its elevations are counted from, and the unit of
        each value column the record carries. The prose that used to say these
        things in the caveats goes, because two statements of one fact are how
        the two drift apart and no filter can read a sentence.

        The row is stated from the dataset's own documentation, never inferred
        from a fetched body: a guessed extent is indistinguishable from a
        measured one to every reader downstream, and this row is what decides
        which source fills a slot. A source that states none is never matched -
        it stays model-callable, and nothing here can say whether it reaches
        this place.

        The UNIT is per value column, because one record carries more than one
        quantity: a gauge reports a discharge in cubic feet per second beside a
        stage in feet, and a slot that read either in the unit it wanted would
        be reading a different river. A source that serves two classes carries
        ONE ROW PER CLASS AND KIND rather than a hybrid word, and each row names
        the columns its value, its window, the zero it is counted from and the
        moment a single reading was taken arrive under - a slot that states a need cannot name a column of a source it
        did not choose. A gauge that reports a measured series and a predicted
        one of the same class carries a row for each, and each row carries the
        request values it is fetched under, because the row is what the match
        weighed and a row default answers for whichever row it was written
        around. A request value written as a NEED ATTRIBUTE rather than a
        literal is the row mapping one of the need's own generic facts - how far
        the question reaches, the place it is asked at - onto the param this
        source states it in, so a question states its opinion once and every
        source hears it in its own words. A unit or a zero the RECORD carries
        per feature is stated as "record" and read off the feature.

        A STATION SET LISTS ITS STATIONS - inline where the set is small, read
        from a bounded listing that is cached once, or discovered by box inside
        the region where the network has no listing at all - because a ring
        alone says a place is inside the region and nothing about whether a
        station stands anywhere near it, which is the distance the reach is
        measured against. A set that lists them is measured from the nearest
        listed station; a discovered network is measured from the region and
        the probe drops it on an empty answer. Rings alone under a station set
        are refused.
        */
    }

    requirement def ASlotStatesANeedAndTheMatchFillsIt {
        doc /*
        A RUNTIME SLOT STATES THE CLASS IT NEEDS AND NAMES NO FETCHER. The slot
        is the TYPE THE ROW STATES - one list of types, each with its ingestion
        and the classes it reads - and the row is named freely: a class the
        stated type does not read refuses where it is written, a row that
        states no type is a plain one, a run solves over exactly one domain and
        one bed, and a record type may be stated more than once. The
        modifiers are absence and the sentence an absence carries. A need
        is one class of the coarse data-class vocabulary; the window and the
        frame it is matched under are the RUN's - the deck's own duration from
        the moment the run asks at, the frame the bed states - and the place is the
        domain's centre unless the row states the point it is asked at.
        WHAT OF THE CLASS the row asks for is the word the answering
        source publishes it under: the published variable a record is a
        measurement of, and on the DOMAIN the KIND the equations are solved
        over. A domain's kind is a fact of the PLACE, read off the word the
        service that resolved it already published and turned by the domain
        slot into the word the sources publish that feature under, so a
        question never carries the narrowing itself. A seed nothing said a type
        for is unclassified and every row of the class is ranked. Where the
        seed CANNOT imply the kind - the land draining through a pour point,
        the water inside a box drawn over land and water - the template states
        its domain's kind as one word on the need, and a stated kind wins.

        A SLOT MAY DECLARE ROWS BESIDE ITS OWN. What fills a slot is not always
        one artifact: a place on a flowline reaches the domain as a line, and a
        line is not something the equations are solved over. The slot states
        the rows it needs - the water surface the line runs between - and the
        runtime produces each through the match, under the slot, the way the
        slot's own class is produced; the cut between them is the slot's
        own coercion. Declaring a need is not fetching.

        NO ROW STATES A UNIT. What a measured slot's record is read in is the
        unit of the KEYWORD its role fills, which the engine's transform fixes,
        or - where the row names the PUBLISHED VARIABLE it observes - that
        variable's own unit off the run's published table: a measurement and the
        thing it is a measurement of are comparable in one unit and no other, so
        the ingestion's opening value and the residual a pairing takes go
        through one conversion. A row that names a variable this run publishes
        no unit under refuses rather than reading the record in whatever its
        source published. How far the question's domain REACHES is the one
        opinion a row still states about its own extent, and it states it
        generically: the answering source's row maps it onto the param
        that source calls it by, and a row that states none leaves the param off
        the call so the source's own default answers.

        The filter is mechanical: class and place are hard, the window is hard
        for a SERIES source and never for a static surface - a 2014 survey
        answers a 2026 question and recency ranks it - and a differing datum is
        FLAGGED rather than filtered, because the offset row is what refuses at.
        A station set states the REACH one station serves, read against the
        nearest station the row lists, and a place further from it than that is
        not a survivor at all. A DISCHARGE is the water passing one section, so
        its place filter is the domain itself: the gauge has to stand on this
        domain's own water - inside the polygon the run drew, or its box, within
        the cell the mesh resolves - and a gauge on another river is dropped by
        name however near it stands. A level propagates up a reach, so the reach
        stays its rule. What the top survivor is CALLED with closes
        through the match: the run's box and window, the matched row's own
        request values, and the nearest listed station where the source is
        called by a station name. A source whose required params the row can
        answer for is a survivor; one whose it cannot is dropped by name. The sort is on facts, in the
        order they decide: how the numbers were come by - measured, then
        predicted, then modelled - how far the place is from them, the cell
        against the mesh, how current the record is, and whether the source is
        already on the run's frame. The top
        survivor is CALLED and dropped on an empty source, so the list a reader
        sees says what the world answered rather than what the sort preferred,
        and a refusal NAMES every source and what each one had to say.

        One run-level statement loosens one filter - a stand-in window, a datum
        taken unconverted - and one names the PICK for a slot among the
        survivors; both show as the user's choice, never as the match's own
        judgement, and a named source the filters excluded is a refusal rather
        than a way past them.

        The bed takes the row its class ranked first, and each next ranked row
        while the water is left a wet hole, or the layer a person hands it by id. A row of soundings is laid on the bed
        grid and filled at the slot. What that row does not
        cover is the surface's own coverage feedback to state.
        */
    }

    requirement def ASeaStateIsAReservedSlot {
        doc /*
        THE SEA STATE AT AN OPEN BOUNDARY IS A SLOT OF ITS OWN, not a composite
        and not an observation under another name. It is the same kind of thing
        as the weather over a domain - one record of several measured columns -
        so it is a type on the one list, serving one class, and the match
        fills it the way it fills every other need.

        A quantity is read off the column stated in that quantity's own unit -
        a record stating two columns in one unit refuses rather than taking the
        first - and the journal says the buoy, how far off it stands, the
        moment and what it reported.

        A PRESCRIBED SEA STATE NEEDS AN EDGE TO ENTER BY. The deck that imposes
        one states the depth a boundary stretch has to reach for it to be
        designated open, as its own starting value, and every stretch that reaches it
        opens; no deck inherits the meshing library's own default, which is set
        for a shelf-scale domain and is deeper than every node of a nearshore
        window. A mesh where nothing reaches the stated depth is sealed, and one
        settle refuses it for every deck that prescribes a sea state, naming the
        deck and the depth it stated - a sealed domain solves green with every
        wave answer zero, which is the one failure a reader cannot see.
        */
    }

    requirement def ARecordSlotHoldsWhatWasMeasured {
        doc /*
        THE WEATHER, THE RAIN AND THE SEA STATE ARE INGESTED AS WHAT WAS
        MEASURED, in words no engine owns: which station or buoy, the quantity,
        its unit, its instants. Nothing under inputs/ names a keyword, a file
        or a module, and nothing there imports a workflow.

        The weather is ONE STATION: the nearest whose record brackets the
        run's window - nearest to the point its row names, else to the middle
        of the run's domain - and no station further off is tried for what
        that one lacks. Every quantity its network reports is kept as a series
        of its own, so an hour one instrument missed costs the others nothing;
        a quantity the station is short of over the window is named with why.
        The rain is the depth per interval at the record's OWN cadence - the
        median gap between its stamps - each instant opening the interval its
        depth fell over; a gap of one and a half cadences or more is a HOLE,
        refused naming the stamps either side. The sea state is a height, a
        period and the bearing the waves come FROM.

        A SLOT ASKS ONLY THE SOURCES ITS INGESTION READS: the weather reads
        station points and the rain a record, so a gridded product serving the
        same class is excluded by the match and never fetched.

        THE ENGINE holds only its reading of them: which quantities this run's
        modules read, the mnemonic or keyword each becomes, and the one clock
        its table is written on. It refuses BY NAME a column it reads that the
        station is short of, reads its own constant for one the network does
        not report and says so, and says on the journal each turn it makes of
        a measured value - a frequency off a period, a bearing run toward.
        */
    }

    requirement def TheRankedListIsOneObjectInThreeViews {
        doc /*
        The list a slot was filled from is ONE object. The card renders it with
        the pick highlighted; the tool result carries the rows only on a TIE,
        where several sources rank equal on every fact the sort reads and the
        model or the user picks by row; the sheet stores the pick and its
        reason.

        The sentence the model is given IS the sentence the card shows. It is
        authored once, in the match, because a second rendering of the same
        facts is a second chance to say something the run did not do.
        */
    }

    requirement def ADataSourceIsReachedThroughOneDoor {
        doc /*
        No data source is a tool the model is told of or ranks: the prompt
        names none, the declared sets and the tool index skip every fetcher, and the
        model reaches one by asking find_sources and calling fetch with the
        row's source and ask. A call to fetch IS a call of the source it names,
        translated before anything keys on a tool name, so the gates, the
        cache, the reuse guard and the emission seam behave exactly as for a
        direct call and a layer lands once. A source or an argument that does
        not exist is refused by name with the nearest.
        */
    }

    requirement def ASeriesIsAlignedToTheRunsEventTime {
        doc /*
        A run opens at the moment it asks about, INSIDE the record: t=0 is that
        instant and the readings before it carry negative times, rather than the
        record's first sample standing in for a moment nobody asked about. A
        record that does not span the window the run solves over refuses, naming
        the nearest sample it holds and the statement that would take it as a
        stand-in - reading a record flat past its last sample is a forcing
        nobody measured.

        A record is read in the unit it was MEASURED in, off its source's
        row where the record carries no unit column of its own; a
        record that states none refuses rather than being read in the unit the
        slot wanted. And a gauge publishes a HEIGHT above its own zero, which is
        a different surface from the one a bed is painted on: the run reaches
        that surface by adding the zero's own elevation, which the site record
        publishes, and a gauge that publishes none refuses.
        */
    }

    requirement def AStoppedRungNeverShips {
        doc /*
        SIGNED DECISION - load-bearing unverified items are verified live before
        any rung ships, and a dead assumption stops its rung rather than
        shipping it. Two rungs the methodology names stopped on measured
        grounds and are absent here rather than declared:

        eHydro, the navigable primary: its queryable surface is one layer of
        survey-boundary polygons carrying a horizontal projection and no
        vertical datum field at all, with the soundings behind per-survey bulk
        archives on another host. A LADDER RUNG has to state its datum on the
        row, before it fetches, so it cannot be one - and what the
        methodology leaves under it is BlueTopo alone, which is not a
        degradation path either. The navigable class therefore has no ladder and
        refuses, naming the stopped primary.

        That is a statement about LADDERS, not about eHydro. A survey states its
        own zero on its own features - a local project datum on many rivers -
        and that is read where the soundings are, so eHydro is a DATA row of its
        own: the row states the datum per feature, the surface derived from it
        carries what those features stated, and the merge that places it over a
        terrain surface refuses two different zeros BY NAME. A per-source zero
        and a per-row zero are both stated; neither is ever assumed.

        NXSDB, the small-stream primary: its measurements carry depth below the
        water surface and no bed elevation and no vertical datum, published as
        one national GeoPackage on a host serving no range requests. That is a
        producer's input, not a bed anyone can fetch.

        So the small-stream class likewise has no rung and REFUSES, naming both
        gaps and the synthetic slot below them.

        That slot is DEFERRED, not merely unbuilt: no synthetic bathymetry is
        produced, the Bieger regression the methodology named as the candidate
        does not build, and whether a fabricated bed may ever stand in for a
        survey is a USER decision rather than a gap for an implementation to
        close. Best-case behaviour is established first and never intertwined
        with sad-path interpolation. The slot is therefore STATED and EMPTY -
        an absence somebody decided, so that a later reader finds a decision
        where they would otherwise find an oversight. Empty, it is a refusal,
        and the refusal is the honest floor working.
        */
    }

    requirement def TheShorelineIsTheDomainsOwnEdge {
        doc /*
        A shoreline is where the water meets land. The DOMAIN is the closed
        polygon the equations are solved over, so its own boundary - islands
        included - is that shoreline, minus the stretches a run of type inflow,
        outflow, open or rating_curve names, which are the edge the water
        CROSSES. Every sizing function measures what is left, on any domain: a
        drawn pond, a reach section, a harbour basin.

        There is therefore ONE mesher path and no box extent: a box is not a
        domain, and cutting the water out of one is a derive over that box and a
        mapped coastline, useful on its own and written as a DATA row by the
        template that wants it. A domain whose whole edge is crossed has no
        shore for a sizing function to measure and is refused by name.
        */
    }

    requirement def TheDomainIsOneSlotHoweverItIsFilled {
        doc /*
        A template solves over any body of water: drawn, picked, fetched, or
        purely surveyed. The DOMAIN is one row - a closed polygon, geometry only
        - and nothing downstream branches on where it came from, because the
        moment a consumer can tell, half the ways of filling it stop working.

        A slot that names a producer is still on the WIRE: what the user hands in
        supersedes the source the template preferred, and that is the whole of
        how a body of water no fetcher knows gets modelled. Fetchers are one way
        to fill a slot, never the linchpin.

        A domain read as TEXT is the name it was given, else the word: the mesh
        session, the layer titles and the run's own name are all written from
        it, so a domain that read as its geometry named every one of them after
        its coordinates.
        */
    }

    requirement def OneBedOverEverySourceAUserCanHave {
        doc /*
        The bed is one seam fed by whatever the user has: a fetched DEM, a
        bathymetry or survey raster, or a stated depth below the free surface.
        It is one row; a layer of soundings is laid on the grid and filled.

        A bed built from a survey over a wider surface is a SECOND SURFACE
        HANDED THE SAME SLOT, not a tool: the slot takes an ordered list, lays
        it first wins with a band recording which won at each cell, and fills
        what is left inside the cut by the bed settings, as its own coercion -
        no one would lay surfaces into a bed outside the slot. What the slot
        hands on is one layer, so the mesh, a grid engine and the journal read
        one surface and know nothing of what went into it.

        A node no surface and no fill covers REFUSES by name. Filling the hole
        with the mean of what was covered is a bed nobody measured, and it reads
        as data everywhere downstream.
        */
    }

    requirement def ABoundaryRunIsTwoPointsAndAType {
        doc /*
        A run is two Points on the domain's edge and a type - wall by default,
        inflow, outflow, open. A template or a producer states zero or more, and
        STATING NONE IS AN ANSWER: a closed body has no liquid boundary and its
        mesh has only walls, so nothing is prescribed where nothing is named.

        A PRODUCER that cut its polygon between two faces returns those faces as
        rows of the same artifact, and the domain slot reads them off it: the
        producer names which row is which in its OWN vocabulary, and the slot
        reads that rather than asking a fetcher to speak the slot's. A row
        naming a stretch that prescribes nothing is the wall the edge already
        is, and is not a run.

        A template declares the slot and nothing else about it. What fills it,
        in order: what the caller supplied, the runs the DOMAIN row carries
        because its producer measured them, what the user draws under the
        boundary-run purpose, and then nothing - which is a closed body. A
        question that needs a run and was given none refuses by naming the run
        it lacked, never by opening on a condition nobody stated.
        */
    }

    requirement def ABoxIsNotADomainAndIsItsOwnSlot {
        doc /*
        A box has no shoreline, so it is not a domain and the mesher refuses one
        by name. What it IS is the window a question is asked inside, and a
        question that cuts its domain out of one declares that window as its own
        slot - which is what puts a canvas ask back where the domain's producer
        took it away: a slot with a producer is never drawn, so a harbour whose
        water is CUT would otherwise have nothing a user with nothing can fill.

        One role, one ingestion, one draw purpose: a rectangle picked on the
        canvas, four numbers, a place or a layer's bounds all read as ``.bbox``
        afterwards, and the raster engines fill the same slot with the grid
        window they solve on.
        */
    }

    requirement def ThalwegBurningIsNeverABedSource {
        doc /*
        SIGNED DECISION - thalweg and stream burning stay REJECTED as a bed
        source. Burning lowers DEM cells along a mapped network so flow routing
        honours it: the depth is chosen for ROUTING reasons and bears no
        relation to true bathymetry, and a burned surface is unsuited even for
        measuring local slope. It enforces direction and connectivity and says
        nothing about cross-sectional conveyance. Reading a routing offset as a
        channel depth is precisely the confusion the correct-data-class law
        forbids.

        The rule is written as a dependency: no module on this bed seam may
        reach for the hydrologic-conditioning family, which is where fill,
        resolve-flats and stream-network conditioning live. A bed source that
        imported them would be conditioning terrain and calling the result a
        survey.

        forbid: trid3nt_server.tools.fetchers.ocean.fetch_bluetopo.hooks -> trid3nt_server.tools.derive
        forbid: trid3nt_server.tools.fetchers.ocean.fetch_cudem.hooks -> trid3nt_server.tools.derive
        */
    }

    // ----------------------------------------------------------------- //
    // Allocations
    // ----------------------------------------------------------------- //


    satisfy requirement AKeyedSourceStatesTheKeyItNeeds by firmsDeclaration;
    satisfy requirement AKeyedSourceStatesTheKeyItNeeds by credentialResolver;
    satisfy requirement AKeyedSourceStatesTheKeyItNeeds by keyedSourceCatalog;
    satisfy requirement AKeyedSourceStatesTheKeyItNeeds by keysForm;
    verify requirement AKeyedSourceStatesTheKeyItNeeds by
        "tests/credentials/test_credential_resolver.py::test_keyed_credentials_are_the_rows_that_declare_one";
    verify requirement AKeyedSourceStatesTheKeyItNeeds by
        "tests/server/test_library_http_route.py::test_every_declared_credential_is_listed_once_with_no_key_material";
    verify requirement AKeyedSourceStatesTheKeyItNeeds by
        "tests/credentials/test_credential_resolver.py::test_one_pushed_key_serves_every_row_naming_it";
    verify requirement AKeyedSourceStatesTheKeyItNeeds by
        "tests/fetchers/test_router_cds.py::test_no_stored_key_asks_before_cdsapi_is_touched";
    verify requirement AKeyedSourceStatesTheKeyItNeeds by
        "tests/fetchers/test_router_stations.py::test_keyed_missing_key_refuses_pre_network";
    verify requirement AKeyedSourceStatesTheKeyItNeeds by
        "tests/plugin/test_keys_form.py::test_one_row_per_credential_not_per_source";

    satisfy requirement AKeyedProviderRowsKeyNeverLeavesTheSession by borrowedProviderExecutor;
    satisfy requirement AKeyedProviderRowsKeyNeverLeavesTheSession by borrowedProviderSession;
    satisfy requirement AKeyedProviderRowsKeyNeverLeavesTheSession by credentialStore;
    verify requirement AKeyedProviderRowsKeyNeverLeavesTheSession by
        "tests/fetchers/test_router_qgis_provider.py::test_a_keyed_row_carries_its_credential_NAME_and_no_key";
    verify requirement AKeyedProviderRowsKeyNeverLeavesTheSession by
        "tests/plugin/test_layer_request.py::test_open_attaches_the_stored_config_id";
    verify requirement AKeyedProviderRowsKeyNeverLeavesTheSession by
        "tests/plugin/test_layer_request.py::test_materialise_attaches_the_stored_config_id";
    verify requirement AKeyedProviderRowsKeyNeverLeavesTheSession by
        "tests/plugin/test_layer_request.py::test_the_key_value_never_rides_the_uri";
    verify requirement AKeyedProviderRowsKeyNeverLeavesTheSession by
        "tests/plugin/test_layer_request.py::test_no_stored_key_refuses_by_name_toward_the_form";

    satisfy requirement ACatalogReaderCarriesNoProvenance by stacRasterReader;
    satisfy requirement ACatalogReaderCarriesNoProvenance by copernicusDeclaration;
    verify requirement ACatalogReaderCarriesNoProvenance by
        "tests/fetchers/test_router_stac_raster.py::test_float_render_applies_scale_offset_and_fill";
    verify requirement ACatalogReaderCarriesNoProvenance by
        "tests/fetchers/test_router_stac_raster.py::test_mosaic_fuse_is_first_valid_in_search_order";
    verify requirement ACatalogReaderCarriesNoProvenance by
        "tests/fetchers/test_bathymetry_data_seam.py::test_every_bed_capable_row_states_its_vertical_datum";

    verify requirement WaterNothingMeasuredIsFilledOnlyWithinTheStatedReach by
        "tests/telemac/test_telemac_run_identity.py::test_what_the_cut_covers_is_on_the_card_before_the_solve";
    satisfy requirement WaterNothingMeasuredIsFilledOnlyWithinTheStatedReach by bedSlot;
    satisfy requirement WaterNothingMeasuredIsFilledOnlyWithinTheStatedReach by bedComposer;
    verify requirement WaterNothingMeasuredIsFilledOnlyWithinTheStatedReach by
        "tests/inputs/test_bed_merge.py::test_a_hole_past_the_fill_s_reach_refuses_naming_the_setting_and_another_surface";
    verify requirement WaterNothingMeasuredIsFilledOnlyWithinTheStatedReach by
        "tests/inputs/test_bed_merge.py::test_water_past_every_surface_s_edge_is_a_hole_the_fill_reaches_or_refuses";
    verify requirement WaterNothingMeasuredIsFilledOnlyWithinTheStatedReach by
        "tests/runtime/test_matched_slots.py::test_a_wet_hole_past_the_fill_s_reach_is_refused_naming_the_setting";
    verify requirement WaterNothingMeasuredIsFilledOnlyWithinTheStatedReach by
        "tests/inputs/test_bed_merge.py::test_a_hole_inside_the_cut_is_filled_and_marked_and_one_outside_is_left";
    verify requirement WaterNothingMeasuredIsFilledOnlyWithinTheStatedReach by
        "tests/inputs/test_bed_merge.py::test_the_fill_reads_inside_the_cut_alone";
    verify requirement WaterNothingMeasuredIsFilledOnlyWithinTheStatedReach by
        "tests/inputs/test_bed_merge.py::test_linear_is_one_setting_away";
    verify requirement WaterNothingMeasuredIsFilledOnlyWithinTheStatedReach by
        "tests/inputs/test_bed_merge.py::test_an_engine_laying_its_own_ladder_neither_merges_nor_fills";
    satisfy requirement AFreeSurfaceAndABedShareOneStatedDatum by lakeLevelDeclaration;
    satisfy requirement AFreeSurfaceAndABedShareOneStatedDatum by lakeDeclaration;
    satisfy requirement AFreeSurfaceAndABedShareOneStatedDatum by freeSurfaceReader;
    verify requirement AFreeSurfaceAndABedShareOneStatedDatum by
        "tests/telemac/test_telemac3d_stratified_flow.py::test_the_level_is_ranked_against_the_domain";
    verify requirement AFreeSurfaceAndABedShareOneStatedDatum by
        "tests/inputs/test_slot_inputs.py::test_each_slot_reads_through_the_ingestion_its_role_names";
    verify requirement AFreeSurfaceAndABedShareOneStatedDatum by
        "tests/telemac/test_open_water_domains.py::test_the_thermocline_is_stated_below_the_water_top_not_the_datum";
    verify requirement AFreeSurfaceAndABedShareOneStatedDatum by
        "tests/inputs/test_vertical_datum.py::test_a_layer_states_its_own_datum_and_a_name_reads_its_row";

    satisfy requirement BedSourceStatesItsDatum by blueTopoSource;
    satisfy requirement BedSourceStatesItsDatum by blueTopoDeclaration;
    satisfy requirement BedSourceStatesItsDatum by bedResultModel;
    verify requirement BedSourceStatesItsDatum by
        "tests/fetchers/test_bathymetry_data_seam.py::test_a_tile_that_states_navd88_passes_the_datum_gate";
    verify requirement BedSourceStatesItsDatum by
        "tests/fetchers/test_bathymetry_data_seam.py::test_a_tile_that_states_no_navd88_refuses_rather_than_merging";
    verify requirement BedSourceStatesItsDatum by
        "tests/fetchers/test_bathymetry_data_seam.py::test_the_envelope_states_the_datum_in_provenance";
    verify requirement BedSourceStatesItsDatum by
        "tests/fetchers/test_bathymetry_data_seam.py::test_the_bluetopo_spec_declares_the_delegate_hooks_and_the_result_model";

    satisfy requirement OneSourceReadsOnOneStatedDatum by bedPainter;
    satisfy requirement OneSourceReadsOnOneStatedDatum by lakeDeclaration;
    satisfy requirement OneSourceReadsOnOneStatedDatum by cudemDeclaration;
    satisfy requirement OneSourceReadsOnOneStatedDatum by etopoDeclaration;
    satisfy requirement OneSourceReadsOnOneStatedDatum by regionalCoastalDemDeclaration;
    satisfy requirement OneSourceReadsOnOneStatedDatum by blueTopoDeclaration;
    verify requirement OneSourceReadsOnOneStatedDatum by
        "tests/fetchers/test_bathymetry_data_seam.py::test_every_bed_capable_row_states_its_vertical_datum";
    verify requirement OneSourceReadsOnOneStatedDatum by
        "tests/fetchers/test_bathymetry_data_seam.py::test_the_lake_row_pins_one_product_of_the_mixed_mosaic";
    verify requirement OneSourceReadsOnOneStatedDatum by
        "tests/mesh/test_mesh_topology_and_bed.py::test_a_row_that_states_no_datum_is_not_a_bed";
    verify requirement OneSourceReadsOnOneStatedDatum by
        "tests/mesh/test_mesh_topology_and_bed.py::test_the_bed_card_states_the_datum_and_the_acquisition_of_its_source";
    verify requirement OneSourceReadsOnOneStatedDatum by
        "tests/fetchers/test_emit_on_fetch_seam.py::test_input_layer_name_shape_and_purpose";
    verify requirement OneSourceReadsOnOneStatedDatum by
        "tests/fetchers/test_router_spec_loader.py::test_a_row_stating_its_datum_as_prose_is_refused";
    verify requirement OneSourceReadsOnOneStatedDatum by
        "tests/fetchers/test_router_spec_loader.py::test_a_row_stating_a_served_frame_or_the_record_loads";

    satisfy requirement ASourceStatesWhatItCovers by coverageContract;
    satisfy requirement ASourceStatesWhatItCovers by gaugeDeclaration;
    satisfy requirement ASourceStatesWhatItCovers by lakeDeclaration;
    verify requirement ASourceStatesWhatItCovers by
        "tests/fetchers/test_rows.py::test_every_spec_loads_and_its_rows_validate";
    verify requirement ASourceStatesWhatItCovers by
        "tests/fetchers/test_rows.py::test_a_source_with_no_row_says_it_is_model_callable";
    verify requirement ASourceStatesWhatItCovers by
        "tests/fetchers/test_rows.py::test_a_station_row_lists_its_stations";
    verify requirement ASourceStatesWhatItCovers by
        "tests/fetchers/test_rows.py::test_the_tide_gauge_states_the_record_and_the_prediction_apart";
    verify requirement ASourceStatesWhatItCovers by
        "tests/fetchers/test_rows.py::test_the_nearest_station_is_what_a_listed_set_is_measured_from";
    verify requirement ASourceStatesWhatItCovers by
        "tests/fetchers/test_rows.py::test_every_series_source_states_the_unit_of_its_value_columns";
    verify requirement ASourceStatesWhatItCovers by
        "tests/fetchers/test_rows.py::test_the_gauge_network_states_each_column_on_its_own_row";
    verify requirement ASourceStatesWhatItCovers by
        "tests/fetchers/test_rows.py::test_a_lake_row_covers_its_lake_and_not_the_open_coast";
    verify requirement ASourceStatesWhatItCovers by
        "tests/fetchers/test_router_spec_loader.py::test_a_row_naming_a_class_outside_the_vocabulary_is_refused";
    verify requirement ASourceStatesWhatItCovers by
        "tests/fetchers/test_router_spec_loader.py::test_a_spec_states_no_coverage_by_default";

    satisfy requirement ASlotStatesANeedAndTheMatchFillsIt by needDeclaration;
    satisfy requirement ASlotStatesANeedAndTheMatchFillsIt by domainSlot;
    satisfy requirement ASlotStatesANeedAndTheMatchFillsIt by sourceMatch;
    satisfy requirement ASlotStatesANeedAndTheMatchFillsIt by matchedSlot;
    verify requirement ASlotStatesANeedAndTheMatchFillsIt by
        "tests/inputs/test_place_kind.py::test_the_geocoder_s_word_becomes_the_word_a_source_publishes";
    verify requirement ASlotStatesANeedAndTheMatchFillsIt by
        "tests/inputs/test_place_kind.py::test_a_place_that_is_not_water_says_nothing";
    verify requirement ASlotStatesANeedAndTheMatchFillsIt by
        "tests/runtime/test_feature_ref.py::test_a_domain_states_no_kind_and_the_seed_says_which_water";
    verify requirement ASlotStatesANeedAndTheMatchFillsIt by
        "tests/runtime/test_feature_ref.py::test_the_kind_a_template_states_is_not_overruled_by_the_place";
    verify requirement ASlotStatesANeedAndTheMatchFillsIt by
        "tests/runtime/test_declared_rows.py::test_a_place_on_a_flowline_has_its_water_surface_produced_for_it";
    verify requirement ASlotStatesANeedAndTheMatchFillsIt by
        "tests/runtime/test_declared_rows.py::test_a_declared_row_nothing_measured_refuses_by_name";
    verify requirement ASlotStatesANeedAndTheMatchFillsIt by
        "tests/inputs/test_domain_cut.py::test_a_place_on_a_flowline_declares_the_water_surface_beside_it";
    verify requirement ASlotStatesANeedAndTheMatchFillsIt by
        "tests/inputs/test_domain_cut.py::test_the_cut_domain_carries_its_two_runs_and_the_centerline";
    verify requirement ASlotStatesANeedAndTheMatchFillsIt by
        "tests/search/test_source_match.py::test_one_survivor_fills_the_slot_and_the_sentence_names_the_facts";
    verify requirement ASlotStatesANeedAndTheMatchFillsIt by
        "tests/search/test_source_match.py::test_a_gauge_on_another_river_is_not_this_domain_s_discharge";
    verify requirement ASlotStatesANeedAndTheMatchFillsIt by
        "tests/search/test_source_match.py::test_a_gauge_on_the_reach_survives_the_place_filter";
    verify requirement ASlotStatesANeedAndTheMatchFillsIt by
        "tests/search/test_source_match.py::test_the_reach_still_answers_for_a_water_level_gauge";
    verify requirement ASlotStatesANeedAndTheMatchFillsIt by
        "tests/search/test_source_match.py::test_a_source_too_coarse_for_the_mesh_ranks_below_every_source_that_resolves_it";
    verify requirement ASlotStatesANeedAndTheMatchFillsIt by
        "tests/search/test_source_match.py::test_a_source_already_on_the_run_s_frame_outranks_one_that_needs_a_shift";
    verify requirement ASlotStatesANeedAndTheMatchFillsIt by
        "tests/search/test_source_match.py::test_a_place_no_source_reaches_refuses_naming_what_each_filter_excluded";
    verify requirement ASlotStatesANeedAndTheMatchFillsIt by
        "tests/search/test_source_match.py::test_a_static_survey_older_than_the_run_is_never_dropped_by_the_window";
    verify requirement ASlotStatesANeedAndTheMatchFillsIt by
        "tests/search/test_source_match.py::test_a_series_outside_the_window_refuses_with_the_nearest_record_named";
    verify requirement ASlotStatesANeedAndTheMatchFillsIt by
        "tests/search/test_source_match.py::test_one_run_level_statement_loosens_the_window_as_the_user_s_choice";
    verify requirement ASlotStatesANeedAndTheMatchFillsIt by
        "tests/search/test_source_match.py::test_a_measured_gauge_at_the_place_outranks_a_modelled_grid_over_it";
    verify requirement ASlotStatesANeedAndTheMatchFillsIt by
        "tests/search/test_source_match.py::test_a_measured_gauge_outranks_a_prediction_a_hundred_kilometres_away";
    verify requirement ASlotStatesANeedAndTheMatchFillsIt by
        "tests/search/test_source_match.py::test_a_station_beyond_its_reach_is_not_a_survivor_at_all";
    verify requirement ASlotStatesANeedAndTheMatchFillsIt by
        "tests/search/test_source_match.py::test_a_run_that_picks_a_survivor_takes_it_as_the_user_s_choice";
    verify requirement ASlotStatesANeedAndTheMatchFillsIt by
        "tests/search/test_source_match.py::test_a_run_that_picks_a_source_the_filters_excluded_is_refused";
    verify requirement ASlotStatesANeedAndTheMatchFillsIt by
        "tests/runtime/test_matched_slots.py::test_no_measurement_over_this_domain_refuses_rather_than_reaching_a_class";
    verify requirement ASlotStatesANeedAndTheMatchFillsIt by
        "tests/runtime/test_matched_slots.py::test_the_next_survivor_takes_its_turn_when_the_top_one_held_nothing";
    verify requirement ASlotStatesANeedAndTheMatchFillsIt by
        "tests/runtime/test_matched_slots.py::test_a_need_and_a_producer_on_one_row_is_refused_at_declaration";
    verify requirement ASlotStatesANeedAndTheMatchFillsIt by
        "tests/inputs/test_slot_inputs.py::test_a_row_states_its_slot_and_its_name_is_free";
    verify requirement ASlotStatesANeedAndTheMatchFillsIt by
        "tests/inputs/test_slot_inputs.py::test_a_slot_states_which_classes_it_serves_and_a_row_outside_them_refuses";
    verify requirement ASlotStatesANeedAndTheMatchFillsIt by
        "tests/telemac/test_workflow_owns_its_stages.py::test_two_level_rows_are_legal_and_two_bed_rows_refuse";
    verify requirement ASlotStatesANeedAndTheMatchFillsIt by
        "tests/telemac/test_workflow_owns_its_stages.py::test_a_template_that_writes_no_mesh_row_fills_with_a_supplied_mesh";

    satisfy requirement ADataSourceIsReachedThroughOneDoor by sourceDoorFind;
    satisfy requirement ADataSourceIsReachedThroughOneDoor by sourceDoorFetch;
    verify requirement ADataSourceIsReachedThroughOneDoor by
        "tests/server/test_fetch_dispatch.py::test_a_wrapper_that_does_not_translate_emits_the_layer_twice";
    verify requirement ADataSourceIsReachedThroughOneDoor by
        "tests/server/test_fetch_dispatch.py::test_an_unknown_source_and_an_unknown_argument_are_refused_by_name_with_the_nearest";
    verify requirement ADataSourceIsReachedThroughOneDoor by
        "tests/search/test_find_sources_query.py::test_flood_zones_ranks_the_fema_zones_source_in_the_top_three";
    verify requirement ADataSourceIsReachedThroughOneDoor by
        "tests/search/test_covered_fetchers.py::test_no_source_is_named_in_the_prompt_or_in_any_declared_set_for_thirty_messages";
    satisfy requirement TheRankedListIsOneObjectInThreeViews by rankedListCard;
    satisfy requirement TheRankedListIsOneObjectInThreeViews by rankedListRecord;
    satisfy requirement TheRankedListIsOneObjectInThreeViews by coverageContract;
    verify requirement TheRankedListIsOneObjectInThreeViews by
        "tests/search/test_source_match.py::test_several_equal_on_every_fact_present_as_a_tie";
    verify requirement TheRankedListIsOneObjectInThreeViews by
        "tests/search/test_source_match.py::test_the_ranked_list_carries_at_most_five_rows";

    satisfy requirement ASeaStateIsAReservedSlot by seaStateReader;
    satisfy requirement ASeaStateIsAReservedSlot by slotDoor;
    verify requirement ASeaStateIsAReservedSlot by
        "tests/inputs/test_wave.py::test_the_slot_reserves_the_name_and_reads_the_class_the_buoys_publish";
    verify requirement ASeaStateIsAReservedSlot by
        "tests/inputs/test_wave.py::test_each_quantity_is_read_off_the_column_stated_in_its_own_unit";
    verify requirement ASeaStateIsAReservedSlot by
        "tests/inputs/test_wave.py::test_two_columns_in_one_unit_refuse_rather_than_the_first_being_taken";
    satisfy requirement ARecordSlotHoldsWhatWasMeasured by weatherReader;
    satisfy requirement ARecordSlotHoldsWhatWasMeasured by rainReader;
    satisfy requirement ARecordSlotHoldsWhatWasMeasured by seaStateReader;
    verify requirement ARecordSlotHoldsWhatWasMeasured by
        "tests/inputs/test_weather.py::test_a_bracketing_station_short_of_one_quantity_is_still_the_station";
    verify requirement ARecordSlotHoldsWhatWasMeasured by
        "tests/inputs/test_weather.py::test_a_reading_one_instrument_missed_leaves_the_other_series_whole";
    verify requirement ARecordSlotHoldsWhatWasMeasured by
        "tests/inputs/test_weather.py::test_a_row_naming_no_point_ranks_from_the_middle_of_the_run_s_domain";
    verify requirement ARecordSlotHoldsWhatWasMeasured by
        "tests/telemac/test_telemac_atmosphere.py::test_a_column_the_run_reads_and_the_station_is_short_of_refuses_by_name";
    verify requirement ARecordSlotHoldsWhatWasMeasured by
        "tests/telemac/test_telemac_atmosphere.py::test_a_reading_one_column_missed_is_read_between_that_column_s_neighbours";
    verify requirement ARecordSlotHoldsWhatWasMeasured by
        "tests/inputs/test_rain.py::test_the_interval_is_the_record_s_own_cadence";
    verify requirement ARecordSlotHoldsWhatWasMeasured by
        "tests/inputs/test_rain.py::test_the_interval_is_the_median_gap_and_a_hole_refuses_naming_its_stamps";
    verify requirement ARecordSlotHoldsWhatWasMeasured by
        "tests/runtime/test_feature_ref.py::test_a_slot_asks_only_the_sources_its_ingestion_reads";
    verify requirement ARecordSlotHoldsWhatWasMeasured by
        "tests/telemac/test_telemac_storm.py::test_an_ingested_record_is_written_at_its_own_cadence_from_the_run_s_zero";
    verify requirement ARecordSlotHoldsWhatWasMeasured by
        "tests/telemac/test_telemac_outflow_stage.py::test_the_flow_range_is_the_gross_rain_rate_on_the_meshed_area";
    verify requirement ARecordSlotHoldsWhatWasMeasured by
        "tests/inputs/test_wave.py::test_the_sea_state_carries_no_engine_s_reading_of_it";
    verify requirement ARecordSlotHoldsWhatWasMeasured by
        "tests/telemac/test_inputs_fill_their_keywords.py::test_the_engine_says_the_two_turns_it_makes_of_a_measured_sea_state";
    verify requirement ASeaStateIsAReservedSlot by
        "tests/telemac/test_nearshore_waves_template.py::test_the_seaward_edge_is_opened_so_the_spectrum_has_somewhere_to_enter";
    verify requirement ASeaStateIsAReservedSlot by
        "tests/telemac/test_nearshore_waves_template.py::test_a_window_whose_rim_is_all_wall_refuses_rather_than_solving_zeros";
    verify requirement ASeaStateIsAReservedSlot by
        "tests/telemac/test_wave_driven_currents_template.py::test_the_seaward_rim_is_opened_so_the_tide_and_the_spectrum_both_enter";

    satisfy requirement ASeriesIsAlignedToTheRunsEventTime by seriesOnTheRunsClock;
    satisfy requirement ASeriesIsAlignedToTheRunsEventTime by freeSurfaceReader;
    satisfy requirement ASeriesIsAlignedToTheRunsEventTime by gaugeDeclaration;
    satisfy requirement ASeriesIsAlignedToTheRunsEventTime by matchedSlot;
    verify requirement ASeriesIsAlignedToTheRunsEventTime by
        "tests/inputs/test_observation.py::test_the_run_opens_at_its_own_moment_inside_the_record";
    verify requirement ASeriesIsAlignedToTheRunsEventTime by
        "tests/inputs/test_observation.py::test_a_record_that_stops_before_the_run_does_refuses_naming_the_nearest";
    verify requirement ASeriesIsAlignedToTheRunsEventTime by
        "tests/inputs/test_observation.py::test_a_window_in_no_stated_unit_refuses_rather_than_reading_the_slot_s";
    verify requirement ASeriesIsAlignedToTheRunsEventTime by
        "tests/inputs/test_observation.py::test_the_row_s_column_unit_is_what_a_bare_record_is_read_in";
    verify requirement ASeriesIsAlignedToTheRunsEventTime by
        "tests/inputs/test_observation.py::test_a_gage_height_reaches_the_run_s_frame_over_the_gauge_s_own_zero";
    verify requirement ASeriesIsAlignedToTheRunsEventTime by
        "tests/inputs/test_observation.py::test_a_gauge_that_publishes_no_zero_refuses_rather_than_reading_a_height";
    verify requirement ASeriesIsAlignedToTheRunsEventTime by
        "tests/fetchers/test_router_nwis.py::test_the_window_read_publishes_the_stage_series_beside_the_discharge";
    verify requirement ASeriesIsAlignedToTheRunsEventTime by
        "tests/fetchers/test_router_nwis.py::test_the_read_carries_the_gauge_s_own_zero";
    verify requirement ASeriesIsAlignedToTheRunsEventTime by
        "tests/runtime/test_matched_slots.py::test_a_run_series_is_asked_for_the_window_the_deck_will_solve";

    satisfy requirement AConsumedObjectIsPinnedWhileItsCaseLives by cacheRetention;
    verify requirement AConsumedObjectIsPinnedWhileItsCaseLives by
        "tests/server/test_store_retention.py::test_a_referenced_object_survives_its_ttl";
    verify requirement AConsumedObjectIsPinnedWhileItsCaseLives by
        "tests/server/test_store_retention.py::test_an_unreferenced_object_goes_and_a_current_one_stays";
    verify requirement AConsumedObjectIsPinnedWhileItsCaseLives by
        "tests/server/test_store_retention.py::test_a_deleted_case_releases_its_objects";
    verify requirement AConsumedObjectIsPinnedWhileItsCaseLives by
        "tests/server/test_store_retention.py::test_a_case_held_object_no_run_names_survives_and_is_released";

    satisfy requirement TheStoreIsReachedByItsOwnSettings by objectStore;
    verify requirement TheStoreIsReachedByItsOwnSettings by
        "tests/server/test_store_settings.py::test_a_chart_spec_persists_on_the_store_s_settings_not_ambient_credentials";
    verify requirement TheStoreIsReachedByItsOwnSettings by
        "tests/server/test_store_settings.py::test_a_store_with_no_endpoint_stated_refuses_rather_than_reach_a_cloud";

    satisfy requirement TheRunHasOneVerticalFrame by verticalFrame;
    satisfy requirement TheRunHasOneVerticalFrame by frameLever;
    satisfy requirement TheRunHasOneVerticalFrame by bedSlot;
    satisfy requirement TheRunHasOneVerticalFrame by bedComposer;
    verify requirement TheRunHasOneVerticalFrame by
        "tests/inputs/test_bed_merge.py::test_a_survey_of_depths_is_read_onto_the_run_s_frame_through_its_own_shift";
    verify requirement TheRunHasOneVerticalFrame by
        "tests/inputs/test_bed_merge.py::test_each_surface_is_moved_onto_the_frame_by_its_own_offset";
    verify requirement TheRunHasOneVerticalFrame by
        "tests/inputs/test_bed_merge.py::test_the_datum_quantity_and_shift_survive_fetch_and_qgis_into_the_bed";
    verify requirement TheRunHasOneVerticalFrame by
        "tests/inputs/test_bed_merge.py::test_a_surface_no_offset_bridges_refuses_naming_both_frames";
    verify requirement TheRunHasOneVerticalFrame by
        "tests/fetchers/test_router_ehydro_surveys.py::test_the_layer_records_the_datum_and_the_shift_its_surveys_publish";
    verify requirement TheRunHasOneVerticalFrame by
        "tests/fetchers/test_router_ehydro_surveys.py::test_surveys_on_one_frame_publish_one_shift_and_two_frames_refuse";
    satisfy requirement TheRunHasOneVerticalFrame by fetcherRouter;
    satisfy requirement TheRunHasOneVerticalFrame by freeSurfaceReader;
    satisfy requirement TheRunHasOneVerticalFrame by offsetRowDeclaration;
    verify requirement TheRunHasOneVerticalFrame by
        "tests/runtime/test_domain_bed_and_context_slots.py::test_every_elevation_slot_is_read_on_the_runs_own_vertical_frame";
    verify requirement TheRunHasOneVerticalFrame by
        "tests/inputs/test_vertical_datum.py::test_a_survey_reaches_the_runs_frame_through_the_shift_it_publishes";
    verify requirement TheRunHasOneVerticalFrame by
        "tests/inputs/test_vertical_datum.py::test_a_source_publishing_no_shift_owes_an_offset_row";
    verify requirement TheRunHasOneVerticalFrame by
        "tests/inputs/test_vertical_datum.py::test_the_coercion_reads_the_rows_value_and_fetches_nothing";
    verify requirement TheRunHasOneVerticalFrame by
        "tests/runtime/test_domain_bed_and_context_slots.py::test_the_runtime_declares_the_offset_row_a_differing_source_owes";
    verify requirement TheRunHasOneVerticalFrame by
        "tests/inputs/test_vertical_datum.py::test_a_pair_nothing_measures_refuses_naming_both_frames";
    verify requirement TheRunHasOneVerticalFrame by
        "tests/inputs/test_slot_inputs.py::test_the_bed_slot_says_which_shape_it_was_handed";
    verify requirement TheRunHasOneVerticalFrame by
        "tests/fetchers/test_router_ehydro_surveys.py::test_a_depth_on_igld85_is_counted_from_the_low_water_datum";
    verify requirement TheRunHasOneVerticalFrame by
        "tests/inputs/test_vertical_datum.py::test_a_record_stating_a_chart_datum_asks_for_the_chart_datum";
    verify requirement TheRunHasOneVerticalFrame by
        "tests/inputs/test_vertical_datum.py::test_a_record_stating_a_datum_no_service_serves_refuses_by_name";
    verify requirement TheRunHasOneVerticalFrame by
        "tests/inputs/test_vertical_datum.py::test_a_record_on_the_runs_frame_is_read_on_it_and_not_shifted";
    verify requirement TheRunHasOneVerticalFrame by
        "tests/inputs/test_vertical_datum.py::test_a_footprint_missing_the_box_centre_is_asked_at_the_seed";
    verify requirement TheRunHasOneVerticalFrame by
        "tests/inputs/test_vertical_datum.py::test_a_seed_off_the_footprint_is_asked_at_the_nearest_measured_point";
    verify requirement TheRunHasOneVerticalFrame by
        "tests/inputs/test_vertical_datum.py::test_a_point_the_service_does_not_reach_refuses_naming_it";
    verify requirement TheRunHasOneVerticalFrame by
        "tests/runtime/test_domain_bed_and_context_slots.py::test_an_offset_row_is_asked_where_the_source_measured_not_at_the_seed";
    verify requirement TheRunHasOneVerticalFrame by
        "tests/inputs/test_slot_inputs.py::test_a_bed_the_runs_frame_cannot_reach_names_its_zero_once";

    satisfy requirement AStoppedRungNeverShips by blueTopoSource;
    satisfy requirement AStoppedRungNeverShips by cudemDeclaration;
    satisfy requirement AStoppedRungNeverShips by regionalCoastalDemDeclaration;
    verify requirement AStoppedRungNeverShips by
        "tests/fetchers/test_bathymetry_data_seam.py::test_a_tile_row_with_no_delivered_link_is_not_data";
    verify requirement AStoppedRungNeverShips by
        "tests/fetchers/test_bathymetry_data_seam.py::test_an_aoi_no_delivered_tile_reaches_refuses_by_name";
    verify requirement AStoppedRungNeverShips by
        "tests/fetchers/test_bathymetry_data_seam.py::test_an_aoi_no_cudem_tile_reaches_refuses_rather_than_serving_something_else";
    verify requirement AStoppedRungNeverShips by
        "tests/fetchers/test_bathymetry_data_seam.py::test_a_coast_with_no_published_regional_collection_refuses_by_name";
    verify requirement AStoppedRungNeverShips by
        "tests/fetchers/test_bathymetry_data_seam.py::test_a_regional_collection_that_cannot_be_listed_refuses_rather_than_skipping";

    satisfy requirement TheShorelineIsTheDomainsOwnEdge by waterCut;
    satisfy requirement TheShorelineIsTheDomainsOwnEdge by coastlineDeclaration;
    verify requirement TheShorelineIsTheDomainsOwnEdge by
        "tests/mesh/test_mesh_polygon_domain.py::test_the_shoreline_the_sizing_functions_measure_is_the_polygons_own_edge";
    verify requirement TheShorelineIsTheDomainsOwnEdge by
        "tests/mesh/test_mesh_polygon_domain.py::test_a_reach_with_two_open_runs_drops_those_stretches_from_the_shore";
    verify requirement TheShorelineIsTheDomainsOwnEdge by
        "tests/mesh/test_mesh_polygon_domain.py::test_an_island_ring_is_shore_too";
    verify requirement TheShorelineIsTheDomainsOwnEdge by
        "tests/mesh/test_mesh_polygon_domain.py::test_a_domain_whose_whole_edge_is_crossed_refuses_by_name";
    verify requirement TheShorelineIsTheDomainsOwnEdge by
        "tests/mesh/test_mesh_om2d.py::test_a_box_extent_refuses_and_names_the_cut_that_makes_it_a_domain";
    verify requirement TheShorelineIsTheDomainsOwnEdge by
        "tests/mesh/test_mesh_water.py::test_the_water_is_the_side_the_way_does_not_have_its_land_on";
    verify requirement TheShorelineIsTheDomainsOwnEdge by
        "tests/mesh/test_mesh_water.py::test_reversing_the_way_moves_the_water_to_the_other_side";
    verify requirement TheShorelineIsTheDomainsOwnEdge by
        "tests/mesh/test_mesh_water.py::test_a_way_that_ends_inside_the_box_divides_nothing_and_refuses";

    satisfy requirement TheDomainIsOneSlotHoweverItIsFilled by domainSlot;
    satisfy requirement TheDomainIsOneSlotHoweverItIsFilled by slotDoor;
    verify requirement TheDomainIsOneSlotHoweverItIsFilled by
        "tests/runtime/test_domain_bed_and_context_slots.py::test_a_domain_row_is_one_slot_however_it_is_filled";
    verify requirement TheDomainIsOneSlotHoweverItIsFilled by
        "tests/inputs/test_slot_inputs.py::test_a_drawn_ring_a_geojson_polygon_and_a_collection_read_the_same";
    verify requirement TheDomainIsOneSlotHoweverItIsFilled by
        "tests/inputs/test_slot_inputs.py::test_several_polygons_are_one_domain_with_parts";
    verify requirement TheDomainIsOneSlotHoweverItIsFilled by
        "tests/inputs/test_slot_inputs.py::test_a_shape_that_is_not_closed_refuses_rather_than_being_squared_off";
    verify requirement TheDomainIsOneSlotHoweverItIsFilled by
        "tests/telemac/test_workflow_owns_its_stages.py::test_the_domain_and_the_bed_reach_the_wire_as_the_slots_they_are";
    verify requirement TheDomainIsOneSlotHoweverItIsFilled by
        "tests/inputs/test_slot_inputs.py::test_a_domain_says_its_own_name_when_it_is_read_as_text";

    satisfy requirement OneBedOverEverySourceAUserCanHave by bedSlot;
    satisfy requirement OneBedOverEverySourceAUserCanHave by bedPainter;
    satisfy requirement OneBedOverEverySourceAUserCanHave by bedComposer;
    verify requirement OneBedOverEverySourceAUserCanHave by
        "tests/inputs/test_bed_merge.py::test_the_first_surface_wins_where_it_measured_and_the_next_paints_the_rest";
    verify requirement OneBedOverEverySourceAUserCanHave by
        "tests/derive/test_session_tools.py::test_an_output_is_a_case_layer_carrying_what_its_input_carried";
    verify requirement OneBedOverEverySourceAUserCanHave by
        "tests/runtime/test_matched_slots.py::test_an_ordered_list_handed_the_bed_fetches_each_named_source_in_order";
    verify requirement OneBedOverEverySourceAUserCanHave by
        "tests/derive/test_session_tools.py::test_the_bed_slot_takes_a_qgis_output_by_its_id";
    verify requirement OneBedOverEverySourceAUserCanHave by
        "tests/inputs/test_bed_merge.py::test_the_order_of_the_list_is_the_priority";
    verify requirement OneBedOverEverySourceAUserCanHave by
        "tests/inputs/test_bed_merge.py::test_surfaces_with_no_common_ground_refuse";
    verify requirement OneBedOverEverySourceAUserCanHave by
        "tests/scripts/test_live_run_harness.py::test_the_calls_before_the_template_run_in_order_and_chain_their_layers";
    verify requirement OneBedOverEverySourceAUserCanHave by
        "tests/inputs/test_slot_inputs.py::test_the_bed_row_states_one_class_and_carries_no_surface_under_it";
    verify requirement OneBedOverEverySourceAUserCanHave by
        "tests/inputs/test_slot_inputs.py::test_the_bed_slot_says_which_shape_it_was_handed";
    verify requirement OneBedOverEverySourceAUserCanHave by
        "tests/mesh/test_bed_sources_and_runs.py::test_a_stated_depth_is_a_flat_bed_below_the_free_surface";
    verify requirement OneBedOverEverySourceAUserCanHave by
        "tests/mesh/test_bed_sources_and_runs.py::test_the_bed_is_one_source_and_two_are_laid_by_the_slot_before_the_op";
    verify requirement OneBedOverEverySourceAUserCanHave by
        "tests/mesh/test_bed_sources_and_runs.py::test_a_domain_no_source_covers_refuses_by_name";
    verify requirement OneBedOverEverySourceAUserCanHave by
        "tests/inputs/test_bed_soundings.py::test_a_points_layer_becomes_a_filled_raster_bed";
    verify requirement OneBedOverEverySourceAUserCanHave by
        "tests/inputs/test_bed_soundings.py::test_soundings_past_the_reach_leave_a_wet_hole";
    verify requirement OneBedOverEverySourceAUserCanHave by
        "tests/search/test_covered_fetchers.py::test_nothing_of_ours_grids_soundings";

    verify requirement ABoundaryRunIsTwoPointsAndAType by
        "tests/inputs/test_slot_inputs.py::test_a_domain_producer_hands_over_the_runs_it_cut_the_polygon_between";
    satisfy requirement ABoundaryRunIsTwoPointsAndAType by boundaryRunSlot;
    satisfy requirement ABoundaryRunIsTwoPointsAndAType by bedPainter;
    verify requirement ABoundaryRunIsTwoPointsAndAType by
        "tests/inputs/test_slot_inputs.py::test_a_run_is_two_points_on_the_edge_and_a_type";
    verify requirement ABoundaryRunIsTwoPointsAndAType by
        "tests/inputs/test_slot_inputs.py::test_a_drawn_line_is_the_run_between_its_two_ends";
    verify requirement ABoundaryRunIsTwoPointsAndAType by
        "tests/inputs/test_slot_inputs.py::test_a_closed_body_states_no_run_and_prescribes_nothing";
    verify requirement ABoundaryRunIsTwoPointsAndAType by
        "tests/mesh/test_bed_sources_and_runs.py::test_boundary_runs_prescribe_the_roles_their_types_name";
    verify requirement ABoundaryRunIsTwoPointsAndAType by
        "tests/mesh/test_bed_sources_and_runs.py::test_a_closed_body_states_no_run_and_the_mesh_has_only_walls";
    verify requirement ABoundaryRunIsTwoPointsAndAType by
        "tests/mesh/test_bed_sources_and_runs.py::test_runs_and_named_faces_are_the_same_statement";
    verify requirement ABoundaryRunIsTwoPointsAndAType by
        "tests/telemac/test_telemac_open_channel.py::test_a_domain_with_no_inflow_run_has_no_channel_to_open";

    satisfy requirement ABoxIsNotADomainAndIsItsOwnSlot by extentSlot;
    satisfy requirement ABoxIsNotADomainAndIsItsOwnSlot by slotDoor;
    verify requirement ABoxIsNotADomainAndIsItsOwnSlot by
        "tests/inputs/test_slot_inputs.py::test_an_extent_slot_reads_a_box_however_the_caller_named_it";
    verify requirement ABoxIsNotADomainAndIsItsOwnSlot by
        "tests/inputs/test_slot_inputs.py::test_only_the_shapes_a_user_can_draw_are_offered_on_the_canvas";
    verify requirement ABoxIsNotADomainAndIsItsOwnSlot by
        "tests/telemac/test_agitation_template.py::test_the_extent_is_a_slot_the_canvas_offers_a_rectangle_for";
    verify requirement ABoxIsNotADomainAndIsItsOwnSlot by
        "tests/telemac/test_agitation_template.py::test_the_mesh_is_cut_from_the_domain_polygon_and_not_from_a_box";

    satisfy requirement ThalwegBurningIsNeverABedSource by blueTopoSource;
    satisfy requirement ThalwegBurningIsNeverABedSource by cudemDeclaration;
    satisfy requirement ThalwegBurningIsNeverABedSource by etopoDeclaration;
    verify requirement ThalwegBurningIsNeverABedSource by
        "tests/model/test_model_conformance.py::test_the_model_conforms_to_the_tree";
    verify requirement ThalwegBurningIsNeverABedSource by
        "tests/fetchers/test_bathymetry_data_seam.py::test_the_selected_tiles_run_coarsest_first_so_the_finest_paints_last";
}
